// =========================================================================
//  VXLAN SERVICE MODEL
// =========================================================================
module vxlan {

  namespace "http://com/ciscoas/services/vxlan";
  prefix vxlan;

  import ietf-inet-types { prefix inet; }

  import tailf-common { prefix tailf; }

  import tailf-ncs { prefix ncs; }

  organization "Cisco Systems, Inc.";

  contact
    "Cisco Systems, Inc.
     Customer Service

     Postal: 170 West Tasman Drive
     San Jose, CA 95134

     Tel: +1 800 533-NETS";

  description
    "This module contains the VXLAN topology model.

     Copyright (c) 2016 by Cisco Systems, Inc.
     All rights reserved.";


  // =========================================================================
  //  REVISION
  // =========================================================================

  revision 2018-04-23 {
    description
      "Optimizations to the templates using NSO 4.6 features.";
  }

  revision 2018-04-20 {
    description
      "EVPN route-target fixes.";
  }

  revision 2017-06-17 {
    description
      "Enabled configuration of NVE source interface.
       Enabled configuration of switchport mode on tenant facing ports.
       Allow single vlan mode for layer2 DCI.
       Suppress ARP is now configurable on routed-topologies.";
  }

  revision 2017-06-07 {
    description
      "Fixed route-target locations.
       Allow 'auto' for route-targets.
       Added option for multicast replication mode (in addition to ingress)";
  }

  revision 2017-04-02 {
    description
      "Added plan-component.";
  }

  revision 2017-03-26 {
    description
      "Updated bridged topologies.";
  }

  revision 2017-03-01 {
    description
      "Customer generalization.";
  }

  revision 2016-12-02 {
    description
      "Initial revision.";
  }


  // =========================================================================
  //  TYPEDEFS
  // =========================================================================

  typedef vnid-type {
    tailf:info "<4096-16777215>;;VNID";
    type uint32 {
      range "4096..16777215";
    }
  }

  typedef vlan-id-type {
    tailf:info "<2-4094>;;VLAN ID";
    type uint16 {
      range "2..4094";
    }
  }

  typedef vlan-name-type {
    type string {
      tailf:info "WORD;;The ascii name for the VLAN (Max Size 128)";
      length "1..128";
    }
  }

  typedef port-channel-id {
    type uint16 {
      range "1..4096";
    }
  }

  typedef ethernet-id {
    type string {
      pattern "[0-9]+.*";
    }
  }

  typedef ipv4-mask {
    description "IPv4 address with integer mask in the format <ipv4 address>/<mask>";
    type string {
      tailf:info "A.B.C.D/LEN;;IP prefix with network mask length";
      pattern
        '(([0-9]|[1-9][0-9]|1[0-9][0-9]|2[0-4][0-9]|25[0-5])\.){3}'
        + '([0-9]|[1-9][0-9]|1[0-9][0-9]|2[0-4][0-9]|25[0-5])'
        + '/(([0-9])|([1-2][0-9])|(3[0-2]))';
    }
  }

  typedef asn2-nn4 {
    type string {
      pattern
         '([1-9][0-9]{0,3}|[1-5][0-9]{1,4}|6[0-4][0-9]{3}|65[0-4][0-9]{2}|655[0-2][0-9]|6553[0-5])'
         + ':'
         + '([1-9][0-9]{0,8}|199999999[0-8]|[1-3][0-9]{1,9}|4[01][0-9]{8}|42[0-8][0-9]{7}|429[0-3][0-9]{6}|4294[0-8][0-9]{5}|42949[0-5][0-9]{4}|429496[0-6][0-9]{3}|4294967[01][0-9]{2}|42949672[0-8][0-9]|429496729[0-5])';
    }
  }

  typedef asn4-nn2 {
    type string {
      pattern
        '([1-9][0-9]{0,8}|199999999[0-8]|[1-3][0-9]{1,9}|4[01][0-9]{8}|42[0-8][0-9]{7}|429[0-3][0-9]{6}|4294[0-8][0-9]{5}|42949[0-5][0-9]{4}|429496[0-6][0-9]{3}|4294967[01][0-9]{2}|42949672[0-8][0-9]|429496729[0-5])'
        + ':'
        + '([1-9][0-9]{0,3}|[1-5][0-9]{1,4}|6[0-4][0-9]{3}|65[0-4][0-9]{2}|655[0-2][0-9]|6553[0-5])';
    }
  }

  typedef ipv4-nn2 {
    type string {
      pattern
        '(([0-9]|[1-9][0-9]|1[0-9][0-9]|2[0-4][0-9]|25[0-5])\.){3}'
        + '([0-9]|[1-9][0-9]|1[0-9][0-9]|2[0-4][0-9]|25[0-5])'
        + ':'
        + '([1-9][0-9]{0,3}|[1-5][0-9]{1,4}|6[0-4][0-9]{3}|65[0-4][0-9]{2}|655[0-2][0-9]|6553[0-5])';
    }
  }

  typedef rt-rd-type {
    description
      "Three allowed types for route target and route distinguishers
         1. ASN2:NN4
         2. ASN4:NN2
         3. IPV4:NN2";
    tailf:info "<1-65535>:<0-4294967295>;;ASN2:index\n" +
               "<65536-4294967295>:<0-65535>;;ASN4:index\n" +
               "<IP address>:<0-65535>;;IPAddress:index ";
    type union {
      type asn2-nn4;
      type asn4-nn2;
      type ipv4-nn2;
    }
  }

  typedef vrf-name-type {
    type string {
      tailf:info "WORD;;Name (Max Size 32)";
      length "1..32";
    }
  }

  typedef route-map-name-type {
    type string {
      tailf:info "WORD;;Route-map name (Max Size 63)";
      length "1..63";
    }
  }

  typedef switchport-mode-type {
    type enumeration {
      enum access {
        tailf:info "Switchport mode access";
      }
      enum trunk {
        tailf:info "Switchport mode trunk";
      }
    }
  }


  // =========================================================================
  //  GROUPINGS
  // =========================================================================

  grouping interface-common-grouping {
    leaf description {
      tailf:info "Interface description";
      type string {
        tailf:info "LINE;;Description, maximum 254 characters";
        length "1..254";
      }
    }
    leaf mode {
      description "Indicate whether this is an access port (i.e. no tagging) or a dot1q trunk port";
      tailf:info "Switchport mode";
      default access;
      type switchport-mode-type;
    }
  } // interface-common-grouping

  grouping interface-grouping {
    container interface {
      tailf:info "Interface type";

      choice interface-type {
        case type-ethernet {
          list Ethernet {
            tailf:info "Ethernet IEEE 802.3z";
            key "id";
            leaf id {
              type ethernet-id {
                tailf:info "<1-66>/<1-128>;;Slot number/Port number";
              }
            }
          }
        }
        case type-port-channel {
          list Port-channel {
            tailf:info "Port Channel interface";
            key "id";
            leaf id {
              type port-channel-id {
                tailf:info "<1-4096>;;Port Channel number";
              }
            }
            container members {
              tailf:info "Member interfaces of the port-channel";
              tailf:cli-add-mode;
              list Ethernet {
                tailf:info "Ethernet member interface";
                tailf:cli-suppress-mode;
                key "member-id";
                leaf member-id {
                  type ethernet-id {
                    tailf:info "<1-66>/<1-128>;;Slot number/Port number";
                  }
                }
              }
            }
          }
        }
      }
    }
  } // interface-grouping

  grouping topology-common-grouping {
    container ports {
      tailf:info "Tenant ports that make the topology";
      tailf:cli-add-mode;

      list leaf-node {
        tailf:info "Leaf node where port is located";
        key "node-name";

        // TODO: Restrict leafs to the ones inside dc-name
        leaf node-name {
          tailf:info "Leaf-node name";
          type leafref {
            path "/vxlan:plant-information/vxlan:plant/vxlan:leaf-node/vxlan:name";
          }
        }
        uses interface-grouping {
          augment "interface/interface-type/type-ethernet/Ethernet" {
            uses interface-common-grouping;
          }
          augment "interface/interface-type/type-port-channel/Port-channel" {
            uses interface-common-grouping;
          }
        }
      }
    } // container ports

    container dci {
      tailf:info "Tenant DCI information";
      tailf:cli-add-mode;

      list vlan {
        tailf:info "DCI VLANs on border-leafs";
        key id;

        leaf id {
          tailf:info "Tenant DCI VLAN ID";
          type vlan-id-type;
        }
        leaf name {
          tailf:info "Tenant DCI VLAN name";
          type vlan-name-type;
        }
      }
    }
  } // topology-common-grouping

  grouping evpn-parameters-grouping {
    leaf vlan-id {
      tailf:info "Tenant VLAN ID";
      type vlan-id-type;
      mandatory true;
    }
    leaf vlan-name {
      tailf:info "Tenant VLAN name";
      type vlan-name-type;
    }
    leaf vni {
      tailf:info "Tenant VNID";
      type vnid-type;
      mandatory true;
    }

    container evpn {
      tailf:info "EVPN parameters";
      tailf:cli-add-mode;

      container route-target {
        tailf:info "Route-target extended communities";
        tailf:cli-add-mode;
        choice route-target-type {
          case auto {
            leaf auto {
              tailf:info "Generate RT automatically (default)";
              type empty;
            }
          }
          case manual {
            leaf import {
              mandatory true;
              tailf:info "Import route-target";
              type rt-rd-type;
            }
            leaf export {
              mandatory true;
              tailf:info "Export route-target";
              type rt-rd-type;
            }
          }
        }
      }

      leaf rd {
        tailf:info "Route Distinguisher";
        type union {
          type enumeration {
            enum "auto" {
              tailf:info "Generate RD automatically (default)";
            }
          }
          type rt-rd-type;
        }
        default "auto";
      }
    } // container evpn
  } // evpn-parameters-grouping

  grouping border-leaf-info-grouping {
    list border-leaf-info {
      config false;
      tailf:cdb-oper {
        tailf:persistent true;
      }
      key node-name;

      leaf node-name {
        type leafref {
          path "/ncs:devices/ncs:device/ncs:name";
        }
      }
      uses interface-grouping {
        augment "interface/interface-type/type-ethernet/Ethernet" {
          leaf vlan-id {
            type vlan-id-type;
          }
          leaf vlan-name {
            type vlan-name-type;
          }
        }
        augment "interface/interface-type/type-port-channel/Port-channel" {
          leaf vlan-id {
            type vlan-id-type;
          }
          leaf vlan-name {
            type vlan-name-type;
          }
        }
      }
    } // list border-leaf-info
  } // border-leaf-info-grouping


  // =========================================================================
  //  PLANT INFORMATION
  // =========================================================================

  container plant-information {
    tailf:info "Information about datacenter environments";
    tailf:cli-add-mode;

    list plant {
      tailf:info "Information for an specific datacenter";
      key dc-name;

      leaf dc-name {
        tailf:info "Datacenter name";
        type string;
      }

      list leaf-node {
        description "All datacenter leafs are catalogued in this list (including border-leafs)";
        tailf:info "Specify devices that are leaf-nodes, including border leafs";
        key name;

        leaf name {
          tailf:info "Device name";
          type leafref {
            path "/ncs:devices/ncs:device/ncs:name";
          }
        }
        // TODO: Include container to hold day0 config parameters to be pushed to the device during onboarding via specified template
      }

      list border-leaf-node {
        description "Contains a subset of leaf-nodes that are assigned as border leafs";
        tailf:info "Specify leaf-nodes that are border-leafs";
        key name;

        leaf name {
          type leafref {
            path "../../leaf-node/name";
          }
        }

		container dci-layer3 {
		  tailf:info "DCI information for routed topologies";
          tailf:cli-add-mode;
          uses interface-grouping;
        }
        container dci-layer2 {
          tailf:info "DCI information for bridged topologies";
          tailf:cli-add-mode;
          uses interface-grouping;
        }
      }
    } // plant

    container global-config {
      tailf:info "Plant global configuration parameters";
      tailf:cli-add-mode;

      leaf tenant-prefix-tag {
        tailf:info "Unicast RIB route tag value for tenant local/direct routes";
        type uint32 {
          tailf:info "<0-4294967295>;;Local/direct tag value";
          range "0..4294967295";
        }
      }
      container tenant-route-maps {
        tailf:info "Define route-map names used for tenant configuration";

        leaf bgp-redistribute-static {
          tailf:info "Route-map applied to redistributed static routes in BGP";
          type route-map-name-type;
        }
        leaf bgp-redistribute-connected {
          tailf:info "Route-map applied to redistributed connected routes in BGP";
          type route-map-name-type;
        }
      }
      leaf nve-source-interface {
        tailf:info "Specify Loopback to be used as source-interface for NVE";
        default "loopback0";
        type string {
          tailf:info "Loopback interface";
          pattern "loopback[0-9]+";
        }
      }
    } // container global-config
  } // container plant-information


  // =========================================================================
  //  SERVICE-POINTS
  // =========================================================================

  augment /ncs:services {

    list vxlan-tenant {
      tailf:info "VXLAN L2/L3 Topologies Service";
      key name;

      leaf name {
        tailf:info "Tenant name";
        type string;
      }

      container topologies {
        tailf:info "Set of topologies belonging to a tenant";

        list bridged-topology {
          tailf:info "Bridged topologies";
          key "name dc-name";

          uses ncs:service-data;
          uses ncs:plan-data;
          ncs:servicepoint vxlan-l2-servicepoint;

          leaf name {
            description "Name for the topology. With L3 topologies, the VRF name is configured with the topology name.";
            tailf:info "Topology name";
            type vrf-name-type;
          }
          leaf dc-name {
            tailf:info "Datacenter for this topology";
            type leafref {
              path "/vxlan:plant-information/vxlan:plant/vxlan:dc-name";
            }
          }

          uses evpn-parameters-grouping;

          leaf replication-mode {
            tailf:info "VXLAN replication mode";
            default "ingress";
            type enumeration {
              enum "ingress" {
                tailf:info "Ingress replication of BUM traffic (default)";
              }
              enum "multicast" {
                tailf:info "Multicast replication of BUM traffic";
              }
            }
          }
          leaf replication-group {
            tailf:info "Multicast group for BUM traffic replication";
            when "../replication-mode = 'multicast'" {
              tailf:dependency "../replication-mode";
            }
            mandatory true;
            type inet:ipv4-address {
              tailf:info "A.B.C.D;;Multicast group IPv4 address";
            }
          }

          uses topology-common-grouping;

          uses border-leaf-info-grouping;

        } // list bridged-topology

        list routed-topology {
          tailf:info "Routed topologies";
          key "name dc-name";

          uses ncs:service-data;
          uses ncs:plan-data;
          ncs:servicepoint vxlan-l3-servicepoint;

          leaf name {
            description "Name for the topology. With L3 topologies, the VRF name is configured with the topology name.";
            tailf:info "Topology name";
            type vrf-name-type;
          }
          leaf dc-name {
            tailf:info "Datacenter for this topology";
            type leafref {
              path "/vxlan:plant-information/vxlan:plant/vxlan:dc-name";
            }
          }

          container sirb {
            tailf:info "Transit L3 VNI information";
            tailf:cli-add-mode;

            uses evpn-parameters-grouping {
              refine vlan-id {
                tailf:info "SIRB VLAN ID";
              }
              refine vlan-name {
                tailf:info "SIRB VLAN name";
              }
              refine vni {
                tailf:info "SIRB VNID";
              }
            }
          }

          leaf vrf-description {
            tailf:info "VRF description";
            type string {
              tailf:info "LINE;;Description, maximum 254 characters";
              length "1..254";
            }
          }

          leaf tenant-as-number {
            tailf:info "Tenant AS number";
            type inet:as-number {
              tailf:info "<1-4294967295>;;Autonomous system number";
            }
            mandatory true;
          }

          leaf replication-mode {
            tailf:info "VXLAN replication mode";
            default "ingress";
            type enumeration {
              enum "ingress" {
                tailf:info "Ingress replication of BUM traffic (default)";
              }
              enum "multicast" {
                tailf:info "Multicast replication of BUM traffic";
              }
            }
          }

          uses topology-common-grouping {
            augment "ports/leaf-node" {
              uses evpn-parameters-grouping;
              leaf tenant-ip-address {
                tailf:info "Tenant IPv4 address";
                type ipv4-mask;
                mandatory true;
              }
              leaf anycast-gateway {
                tailf:info "Enable anycast-gateway";
                type empty;
              }
              leaf suppress-arp {
                description "Suppress ARP is only supported with anycast-gateway";
                tailf:info "Enable ARP suppression";
                when "../anycast-gateway" {
                  tailf:dependency "../anycast-gateway";
                }
                type empty;
              }
              leaf replication-group {
                tailf:info "Multicast group for BUM traffic replication";
                when "../../../replication-mode = 'multicast'" {
                  tailf:dependency "../../../replication-mode";
                }
                mandatory true;
                type inet:ipv4-address {
                  tailf:info "A.B.C.D;;Multicast group IPv4 address";
                }
              }
            }
            augment "dci" {
              leaf dci-as-number {
                tailf:info "DCI AS number";
                type inet:as-number {
                  tailf:info "<1-4294967295>;;Autonomous system number";
                }
                mandatory true;
              }
            }
            augment "dci/vlan" {
              leaf border-leaf-ipv4 {
                tailf:info "Tenant DCI IPv4 address on border-leaf";
                type ipv4-mask;
                mandatory true;
              }
              leaf bgp-neighbor-ipv4 {
                tailf:info "Border-leaf DCI bgp neighbor IPv4 address";
                type inet:ipv4-address {
                  tailf:info "A.B.C.D;;BGP neighbor IPv4 address";
                }
                mandatory true;
              }
              leaf bgp-neighbor-description {
                tailf:info "Border-leaf DCI bgp neighbor description";
                type string {
                  tailf:info "LINE;;Description, maximum 254 characters";
                  length "1..254";
                }
              }
            }
          }

          uses border-leaf-info-grouping;

        } // list routed-topology
      } // container topologies
    } // list vxlan-tenant
  } // augment services
}
